module sonic-1-list {

    yang-version 1.1;

    namespace "http://github.com/Azure/s-1-list";
    prefix s-1-list;

    container sonic-1-list {
        /* sonic-1-list - top level container */

        container TABLE_1 {
            /* TABLE_1 - table container */

            description "TABLE_1 description";

            list TABLE_1_LIST {
                /* TABLE_1 - object container */

                description "TABLE_1_LIST description";

                key "key_name";

                leaf key_name {
                    type string;
                }
            }
        }
    }
}
